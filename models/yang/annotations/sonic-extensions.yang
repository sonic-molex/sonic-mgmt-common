module sonic-extensions {

  yang-version "1";

  // namespace
  namespace "http://openconfig.net/yang/sonic-ext";

  prefix "sonic-ext";

  // meta
  organization "Sonic working group";

  contact
    "OpenConfig working group
    www.openconfig.net";

  description
    "This module provides extensions to the YANG language to allow
    Sonic specific functionality and meta-data to be defined.";

  revision "2019-08-30" {
    description
      "Add extensions for redis DB mappings to identify the Redis DB name.";
  }

  revision "2019-07-26" {
    description
      "Add extensions for redis DB mappings for table, table-keys, table-fields and corresponding transformer methods.";
  }

  revision "2023-05-20" {
    description
      "Add extensions for pre transformer, virtual table support, rpc-callback, cascade-delete, value-transformer, table-owner ";
  }

  // extension statements
  extension table-name {
    argument "table-name";
    description "Db table name.";
  }

  extension key-transformer {
    argument "key-transformer-name";
    description "Db table key transformer name indicating that the list keys together form db table keys.";
  }

  extension key-delimiter {
    argument "key-delimiter-string";
    description "Db table key values delimiter.";
  }

  extension field-name {
    argument "field-name";
    description "Db table field name.";
  }

  extension openapi-opid {
    argument "openapi-opid";
    description "Custom Operation ID for OpenAPI";
  }

  extension field-transformer {
    argument "field-transformer-name";
    description "Db table field transformer name.This can be applied to either transform yang value to some different format
                 or choose a specific DB field based on the type of yang value.";
  }
  
  extension subtree-transformer {
    argument "subtree-transformer-name";
    description "Subtree/node level transformer name that will have db mappings for an entire yang subtree.";
  }

  extension post-transformer {
    argument "post-transformer-name";
    description "Transformer name that will perform post-translation tasks.";
  }

  extension validate-xfmr {
    argument "validate-xfmr-name";
    description "Validation callpoint used to validate a YANG node during data translation.
		 Equivalent to XPath evaluation on when statement";
  }

  extension db-name {
    argument "db-name";
    description "DB name that will indicate where data is stored. Eg: Config DB, App DB etc";
  }
  extension table-transformer {
    argument "table-transformer-name";
    description "Db table transformer name.This can be applied to either transform yang value to some different format
                 or choose a specific DB table based on the type.";
  }

  extension cascade-delete {
    argument "cascade-delete";
    description "Cascade delete extension";
  }

  extension rpc-callback {
    argument "callback";
    description "RPC callback to be invoked for action";
  }

  extension action-callback {
    argument "callback";
    description
      "Action callback to be invoked for action within list or container";
  }

  extension value-transformer {
    argument "value-transformer-name";
    description "Db table field/key value transformer name. This can be applied to transform yang value to some different format.";
  }

  extension table-owner {
    argument "table-owner-flag";
    description  "Indicates table ownership of the redis-db table annotated at the node.
                  The extension is applicable to the nodes annotated with table-name or table-transformer and having no subtree-transformer annotation.
                  The table-owner is deemed to be true unless it is annotated with its value to 'false'.";
  }

  extension virtual-table {
    argument "virtual-table-flag";
    description "Table not present in redis-db.";
  }

  extension pre-transformer {
	  argument "pre-transformer-name";
	  description "Transformer name that will perform pre-translation tasks.";
  }

  extension path-transformer {
    argument "path-transformer-name";
    description "To mention the name of the path transformer which is to resolve the yang uri by filling the
                yang keys in the path using the db table key information";
  }
}
