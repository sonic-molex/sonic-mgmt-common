module openconfig-optical-attenuator-annot {

    yang-version "1";

    namespace "http://openconfig.net/yang/annotation/oc-opt-att-annot";
    prefix "oc-opt-att-annot";

    import sonic-extensions { prefix sonic-ext; }
    import openconfig-optical-attenuator { prefix oc-opt-att; }

    deviation /oc-opt-att:optical-attenuator {
      deviate add {
      }
    }

    deviation /oc-opt-att:optical-attenuator/oc-opt-att:attenuators {
      deviate add {
        sonic-ext:table-name "OTN_ATTENUATOR";
      }
    }

    deviation /oc-opt-att:optical-attenuator/oc-opt-att:attenuators/oc-opt-att:attenuator {
      deviate add {
        sonic-ext:key-transformer "oc_name_key_xfmr";
        sonic-ext:table-transformer "otn_table_xfmr";
      }
    }

    deviation /oc-opt-att:optical-attenuator/oc-opt-att:attenuators/oc-opt-att:attenuator/oc-opt-att:config {
      deviate add {
      }
    }

    deviation /oc-opt-att:optical-attenuator/oc-opt-att:attenuators/oc-opt-att:attenuator/oc-opt-att:config/oc-opt-att:name {
      deviate add {
        sonic-ext:field-transformer "oc_name_field_xfmr";
      }
    }

    deviation /oc-opt-att:optical-attenuator/oc-opt-att:attenuators/oc-opt-att:attenuator/oc-opt-att:config/oc-opt-att:attenuation-mode {
      deviate add {
        sonic-ext:field-name "attenuation-mode";
      }
    }

    deviation /oc-opt-att:optical-attenuator/oc-opt-att:attenuators/oc-opt-att:attenuator/oc-opt-att:config/oc-opt-att:target-output-power {
      deviate add {
        sonic-ext:field-name "target-output-power";
      }
    }

    deviation /oc-opt-att:optical-attenuator/oc-opt-att:attenuators/oc-opt-att:attenuator/oc-opt-att:config/oc-opt-att:attenuation {
      deviate add {
        sonic-ext:field-name "attenuation";
      }
    }

    deviation /oc-opt-att:optical-attenuator/oc-opt-att:attenuators/oc-opt-att:attenuator/oc-opt-att:config/oc-opt-att:enabled {
      deviate add {
        sonic-ext:field-name "enabled";
      }
    }

    deviation /oc-opt-att:optical-attenuator/oc-opt-att:attenuators/oc-opt-att:attenuator/oc-opt-att:state {
      deviate add {
        sonic-ext:db-name "STATE_DB";
        sonic-ext:table-name "OTN_ATTENUATOR_TABLE";
        sonic-ext:key-transformer "oc_name_key_xfmr";
      }
    }

    deviation /oc-opt-att:optical-attenuator/oc-opt-att:attenuators/oc-opt-att:attenuator/oc-opt-att:state/oc-opt-att:name {
      deviate add {
        sonic-ext:field-transformer "oc_name_field_xfmr";
      }
    }

    deviation /oc-opt-att:optical-attenuator/oc-opt-att:attenuators/oc-opt-att:attenuator/oc-opt-att:state/oc-opt-att:attenuation-mode {
      deviate add {
        sonic-ext:field-name "attenuation-mode";
      }
    }

    deviation /oc-opt-att:optical-attenuator/oc-opt-att:attenuators/oc-opt-att:attenuator/oc-opt-att:state/oc-opt-att:target-output-power {
      deviate add {
        sonic-ext:field-name "target-output-power";
      }
    }

    deviation /oc-opt-att:optical-attenuator/oc-opt-att:attenuators/oc-opt-att:attenuator/oc-opt-att:state/oc-opt-att:attenuation {
      deviate add {
        sonic-ext:field-name "attenuation";
      }
    }

    deviation /oc-opt-att:optical-attenuator/oc-opt-att:attenuators/oc-opt-att:attenuator/oc-opt-att:state/oc-opt-att:enabled {
      deviate add {
        sonic-ext:field-name "enabled";
      }
    }

    deviation /oc-opt-att:optical-attenuator/oc-opt-att:attenuators/oc-opt-att:attenuator/oc-opt-att:state/oc-opt-att:component {
      deviate add {
        sonic-ext:field-name "component";
      }
    }

    deviation /oc-opt-att:optical-attenuator/oc-opt-att:attenuators/oc-opt-att:attenuator/oc-opt-att:state/oc-opt-att:ingress-port {
      deviate add {
        sonic-ext:field-name "ingress-port";
      }
    }

    deviation /oc-opt-att:optical-attenuator/oc-opt-att:attenuators/oc-opt-att:attenuator/oc-opt-att:state/oc-opt-att:egress-port {
      deviate add {
        sonic-ext:field-name "egress-port";
      }
    }

    deviation /oc-opt-att:optical-attenuator/oc-opt-att:attenuators/oc-opt-att:attenuator/oc-opt-att:state/oc-opt-att:actual-attenuation {
      deviate add {
      }
    }

    deviation /oc-opt-att:optical-attenuator/oc-opt-att:attenuators/oc-opt-att:attenuator/oc-opt-att:state/oc-opt-att:actual-attenuation/oc-opt-att:instant {
      deviate add {
        sonic-ext:field-name "actual-attenuation";
      }
    }

    deviation /oc-opt-att:optical-attenuator/oc-opt-att:attenuators/oc-opt-att:attenuator/oc-opt-att:state/oc-opt-att:output-power-total {
      deviate add {
      }
    }

    deviation /oc-opt-att:optical-attenuator/oc-opt-att:attenuators/oc-opt-att:attenuator/oc-opt-att:state/oc-opt-att:output-power-total/oc-opt-att:instant {
      deviate add {
        sonic-ext:field-name "output-power-total";
      }
    }

    deviation /oc-opt-att:optical-attenuator/oc-opt-att:attenuators/oc-opt-att:attenuator/oc-opt-att:state/oc-opt-att:optical-return-loss {
      deviate add {
      }
    }

    deviation /oc-opt-att:optical-attenuator/oc-opt-att:attenuators/oc-opt-att:attenuator/oc-opt-att:state/oc-opt-att:optical-return-loss/oc-opt-att:instant {
      deviate add {
        sonic-ext:field-name "optical-return-loss";
      }
    }

}
